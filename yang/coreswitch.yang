module coreswitch {
  yang-version "1";

  namespace "http://coreswitch.io/";
  prefix "coreswitch";

  import ietf-inet-types {
    prefix inet;
  }

  import dhcp {
    prefix dhcp;
  }

  import vrrp {
    prefix vrrp;
  }

  import coreswitch-ntp {
    prefix ntp;
  }

  import coreswitch-ext {
    prefix ext;
  }

  import quagga {
    prefix quagga;
  }

  container vrf {
    list name {
      key "name";
      leaf name {
        type string;
      }
      leaf rd {
        type string;
      }
      leaf hub-node {
        type string;
      }
      leaf distribute-list-ospf {
        type string;
      }
      container dhcp {
        uses "dhcp:dhcp";
      }
      container ntp {
        uses "ntp:ntp";
      }
      container static {
        list route {
          key "prefix";
          leaf prefix {
            type inet:ipv4-prefix;
          }
          list nexthop {
            key "address";
            leaf "address" {
              type inet:ipv4-address;
              description "Nexthop of the route";
            }
          }
          list interface {
            key "ifname";
            leaf "ifname" {
              type string;
            }
          }
          leaf distance {
            type uint8;
            description "Distance of the route.";
          }
        }
      }
      list vrrp {
        key vrid;

        leaf vrid {
          type uint8 {
            range 1..255;
          }
          description "Virtual router ID.";
        }

        leaf interface {
          type string;
          description "Interface name";
        }

        leaf state {
          type enumeration {
            enum master;
            enum backup;
          }
        }

        leaf virtual-address {
          type inet:ipv4-address;
          description "Virtual IPv4 address";
        }

        leaf priority {
          type uint8 {
            range 1..255;
          }
          default 100;
          description
            "Configures the Virtual Router Redundancy Protocol (VRRP)
         election priority for the backup virtual router.";
        }

        leaf advertisement-interval {
          type uint8 {
            range 1..255;
          }
          default 1;
          description
            "Configures the interval that Virtual Router
         Redundancy Protocol Version 2 (VRRPv2) advertisements
         are sent from the specified interface.";
        }

        list unicast-peer {
          key address;
          leaf "address" {
            type inet:ipv4-address;
            description "Other VRRP router's IP address";
          }
        }

        leaf authentication-key {
          type string;
          description
            "VRRP authentication key.  When this is specified, VRRP authentication is enabled.";
        }

        leaf preempt {
          type empty;
          description
            "Enable VRRP preemption.";
        }
      }

    }
  }

  container vlans {
    list vlan {
      key "id";
      leaf id {
        type uint16 {
          range 1..4096;
        }
      }
    }
  }

  container dhcp {
    uses "dhcp:dhcp";
  }

  container vrrp {
    uses "vrrp:vrrp";
  }

  container interfaces {
    list interface {
      key "name";
      leaf name {
        type string;
      }
      leaf vrf {
        type string;
      }
      container ipv4 {
        list address {
          key "ip";
          leaf ip {
            type inet:ipv4-prefix;
          }
        }
        uses quagga:if-ipv4;
      }
      container ipv6 {
        list address {
          key "ip";
          leaf ip {
            type inet:ipv6-prefix;
          }
        }
        uses quagga:if-ipv6;
      }
      leaf shutdown {
        type empty;
      }
      leaf dhcp-relay-group {
        type string;
      }
      leaf descriptionx {
        type string;
      }
      leaf mtu {
        type uint16 {
          range "68..max";
        }
      }
      list vlans {
        key "vlan-id";
        leaf vlan-id {
          type uint16 {
            range 1..4096;
          }
        }
      }
      leaf mode {
        type enumeration {
          enum 1x100G;
          enum 1x40G;
          enum 2x40G;
          enum 2x50G;
          enum 4x10G;
          enum 4x25G;
          enum 4x1G_SGMII;
        }
      }
      leaf fec {
        type enumeration {
          enum RS;
          enum FC;
        }
      }
    }
  }

  container routing-options {
    ext:help "routing-option help";
    leaf router-id {
      type inet:ipv4-address;
    }
    container ipv4 {
      list route {
        key "prefix";
        leaf prefix {
          type inet:ipv4-prefix;
        }
        list nexthop {
          key "address";
          leaf "address" {
            type inet:ipv4-address;
            description "Nexthop of the route";
          }
        }
        list interface {
          key "ifname";
          leaf "ifname" {
            type string;
          }
        }
        leaf distance {
          type uint8;
          description "Distance of the route.";
        }
      }
      list route-srv6 {
        key "prefix";
        leaf prefix {
          type inet:ipv4-prefix;
        }
        list nexthop {
          key "address";
          leaf "address" {
            type inet:ipv4-address;
            description "Nexthop of the route";
          }
          list seg6 {
            key "mode";
            leaf mode {
              type enumeration {
                enum encap;
              }
            }
            leaf-list segments {
              type inet:ipv6-address;
            }
          }
        }
      }
    }
    container ipv6 {
      list route {
        key "prefix";
        leaf prefix {
          type inet:ipv6-prefix;
        }
        list nexthop {
          key "address";
          leaf "address" {
            type inet:ipv6-address;
          }
        }
      }
      list route-srv6 {
        key "prefix";
        leaf prefix {
          type inet:ipv6-prefix;
        }
        list nexthop {
          key "address";
          leaf "address" {
            type inet:ipv6-address;
          }
          list seg6 {
            key "mode";
            leaf mode {
              type enumeration {
                enum inline;
                enum encap;
              }
            }
            leaf-list segments {
              type inet:ipv6-address;
            }
          }
        }
      }
      list localsid { /* update based on draft-raza-spring-srv6-yang */
        key "prefix";
        leaf prefix {
          type inet:ipv6-prefix;
        }
        list nexthop {
          key "address";
          leaf "address" {
            type inet:ipv6-address;
          }
          list action {
            key "action-type";
            leaf action-type {
              type enumeration {
                enum End;
                enum End.X;
                enum End.T;
                enum End.DX2;
                enum End.DX6;
                enum End.DX4;
                enum End.DT6;
                enum End.B6;
                enum End.B6.Encaps;
              }
            }
            leaf-list segments {
              when "../action-type = 'End.B6' || ../action-type = 'End.B6.Encaps'";
              type inet:ipv6-address;
              /* mandatory true; */
            }
            leaf nh6 {
              when "../action-type = 'End.X' || ../action-type = 'End.DX6'";
              type inet:ipv6-address;
              /* mandatory true; */
			}
            leaf table {
              when "../action-type = 'End.T' || ../action-type = 'End.DT6'";
              type uint8 {
                range 1..255;
              }
              /* mandatory true; */
            }
            leaf oif {
              when "../action-type = 'End.DX2'";
              type string;
              /* mandatory true; */
              description "Output interface name";
            }
            leaf nh4 {
              when "../action-type = 'End.DX4'";
              type inet:ipv4-address;
              /* mandatory true; */
            }
          }
        }
      }
    }
    leaf nexthop-walker {
      type empty;
    }
  }

  container protocols {
    ext:help "Routing protocol configuration";
    uses quagga:protocols;
  }

  container policy {
    uses quagga:policy;
  }

  container system {
    description
      "System group configuration.";

    leaf hostname {
      type inet:domain-name;
      description
        "The name of the host.  This name can be a single domain
        label or the fully qualified domain name of the host.";
    }
    container ntp {
      uses "ntp:ntp";
    }
    container etcd {
      list endpoints {
        key "url";
        leaf url {
          type string;
        }
      }
      leaf path {
        type string;
      }
    }
  }
  // ip prefix-list
  list prefix-list {
    key "name";
    leaf name {
      type string;
    }
    // ip prefix-list * description
    leaf description {
      description
        "Prefix-list specific description";
      type string {
        length "1..80";
      }
    }
    list seq {
      // NOTE: the seq element is not actually mandatory
      // in the Cisco CLI. If it isn't give
      description
        "sequence number of an entry";
      key "number";
      leaf number {
        type uint32 {
          range "1..4294967294";
        }
      }
      leaf action {
        mandatory;
        type enumeration {
          enum permit;
          enum deny;
        }
      }
      leaf prefix {
        mandatory;
        type inet:ipv4-prefix;
      }
      leaf ge {
        description
          "Minimum prefix length to be matched";
        type uint8 {
          range "1..32";
        }
      }
      leaf le {
        description
          "Maximum prefix length to be matched";
        type uint8 {
          range "1..32";
        }
      }
      leaf eq {
        description
          "Maximum prefix length to be matched";
        type uint8 {
          range "1..32";
        }
      }
    }
  }
}
